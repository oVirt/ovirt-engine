--
-- Copyright 2014 Red Hat Inc.
--
-- Licensed under the Apache License, Version 2.0 (the "License");
-- you may not use this file except in compliance with the License.
-- You may obtain a copy of the License at
--
--     http://www.apache.org/licenses/LICENSE-2.0
--
--     Unless required by applicable law or agreed to in writing, software
--     distributed under the License is distributed on an "AS IS" BASIS,
--     WITHOUT WARRANTIES OR CONDITIONS OF ANY KIND, either express or implied.
--     See the License for the specific language governing permissions and
--     limitations under the License.
--

REDHAT-MIB DEFINITIONS ::= BEGIN

IMPORTS
    MODULE-IDENTITY, enterprises FROM SNMPv2-SMI
;

redhat MODULE-IDENTITY
    LAST-UPDATED "201409140000Z"
    ORGANIZATION "www.redhat.org"
    CONTACT-INFO "TBD"
    DESCRIPTION  "TBD"
    REVISION     "201409140000Z"
    DESCRIPTION
        "First draft"
    ::= { enterprises 2312}

END
